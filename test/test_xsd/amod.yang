module amod {
  namespace "http://example.com/a";
  prefix a;

  include asub;

  feature abc;

  identity bogus;

  identity foo {
    base bogus;
  }

  identity bar {
    base foo;
  }

  typedef foo-ref {
    type leafref {
      path "/a:top/a:foo";
    }
  }

  container top {

    typedef bool {
      type union {
        type boolean;
        type uint8 {
          range "0|1|2";
        }
        type enumeration {
          enum "yes";
          enum "no";
        }
      }
    }
    leaf foo {
      type int64 {
        range -5..5;
      }
      default "-1";
    }
    leaf-list pac {
      type bool;
    }
    leaf bar {
      type empty;
    }
    leaf barstr {
        type string {
            length "2|7..8|10";
        }
    }
    leaf-list baz {
      type decimal64 {
        fraction-digits 18;
      }
    }
    leaf mek {
      type foo-ref;
    }
    anyxml junk;
    choice ch {
      case ca1 {
        leaf e {
          type empty;
        }
      }
    }
  }
}
